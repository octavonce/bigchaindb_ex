Fingerprints DEFINITIONS AUTOMATIC TAGS ::= BEGIN
  IMPORTS Condition FROM CryptoConditions;

  -- Fingerprint Content
  -- The PREIMAGE-SHA-256 condition fingerprint content is not DER
  -- encoded
  -- The fingerprint content is the preimage
  PrefixFingerprintContents ::= SEQUENCE {
    prefix               OCTET STRING,
    maxMessageLength     INTEGER (0..4294967295),
    subcondition         Condition
  }
  ThresholdFingerprintContents ::= SEQUENCE {
    threshold            INTEGER (1..65535),
    subconditions        SET OF Condition
  }
  RsaFingerprintContents ::= SEQUENCE {
    modulus              OCTET STRING
  }
  Ed25519FingerprintContents ::= SEQUENCE {
    publicKey            OCTET STRING (SIZE(32))
  }
END
